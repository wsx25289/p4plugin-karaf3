module p4plugin-core {
    yang-version 1;
    namespace "urn:opendaylight:p4plugin:core";
    prefix "core";

    organization
        "ZTE corporation";

    contact
        "ding.rui@zte.com.cn";

    description
        "This module contains a set of type definitions and
         RPCs that are used across p4plugin";

    revision "2017-08-08" {
        description "Initial revision.";
    }

    import ietf-inet-types {
        prefix "inet";
        revision-date 2013-07-15;
    }
    
    import ietf-interfaces-test {
        prefix "adapter";
        revision-date 2017-09-08;
    }

    grouping rpc-result {
        leaf result {
            type boolean;
            default false;
        }
    }

    grouping action {
        leaf action-name {
            type string;
        }

        list action-param {
            key "param-name";
            leaf param-name {
                type string;
            }

            leaf param-value {
                type string;
            }
        }
    }

    grouping match-fields {
        list match-field {
            key "field-name";
            leaf field-name {
                type string;
            }

            choice field-match-type {
                default EXACT;
                case EXACT {
                    leaf exact-value {
                        type string;
                    }
                }

                case TERNARY {
                    leaf ternary-Value {
                        type string;
                    }

                    leaf ternary-mask {
                        type string {
                            pattern '([1-9]|[1-2][0-9]|3[0-2])|'                          +
                                    '((([0-9]|[1-9][0-9]|1[0-9][0-9]|2[0-4][0-9]|'        +
                                    '25[0-5])\.){3}([0-9]|[1-9][0-9]|1[0-9][0-9]|2[0-4]'  +
                                    '[0-9]|25[0-5]))';
                        }
                    }
                }

                case LPM {
                    leaf lpm-value {
                        type string;
                    }

                    leaf lpm-prefixLen {
                        type uint8 {
                            range 0..32;
                        }
                   }
                }

                case RANGE {
                    leaf range-high {
                        type uint32;
                    }

                    leaf range-low {
                        type uint32;
                    }
                }

                case VALID {
                    leaf valid-value {
                        type boolean;
                    }
                }
            }
        }
    }

    grouping table-entry {
        leaf table {
            type string;
        }
        uses match-fields;
        choice action-type {
            default DIRECT-ACTION;
            case DIRECT-ACTION {
                uses action;
            }

            case ACTION-PROFILE-MEMBER {
                leaf member-id {
                    type uint32;
                }
            }

            case ACTION-PROFILE-GROUP {
                leaf group-id {
                    type uint32;
                }
            }
        }
    }

    grouping packet-payload {
        leaf payload {
            type binary;
        }
    }

    grouping device-config {
        leaf config-file {
            type string;
        }
    }

    grouping runtime-info {
        leaf runtime-file {
            type string;
        }
    }

    grouping action-profile-member {
        leaf action-profile {
            type string;
        }

        leaf member-id {
            type uint32;
        }

        uses action;
    }

    grouping action-profile-group {
        leaf action-profile {
            type string;
        }

        leaf group-id {
            type uint32;
        }

        leaf group-type {
            type enumeration {
                enum UNSPECIFIED;
                enum SELECT;
                enum FAST_FAILOVER;
            }
        }

        list group-member {
            key "member-id";
            leaf member-id {
                type uint32;
            }

            leaf weight {
                type int32;
            }

            leaf watch {
                type int32;
            }
        }

        leaf max-size {
            type int32;
        }
    }
    
    grouping node {
        leaf node-id {
            type string;
       }
    }
    
    rpc set-pipeline-config {
        input {
            uses adapter:p4-device;
            uses device-config;
            uses runtime-info;
        }

        output {
            uses rpc-result;
        }
    }

    rpc get-pipeline-config {
        input {
            uses node;
        }

        output {
            uses rpc-result;
            leaf Content {
                type string;
            }
        }
    }

    rpc add-table-entry {
        input {
            uses node;
            uses table-entry;
        }

        output {
            uses rpc-result;
        }
    }

    rpc modify-table-entry {
        input {
            uses node;
            uses table-entry;
        }

        output {
            uses rpc-result;
        }
    }

    rpc delete-table-entry {
        input {
            uses node;
            leaf table {
                type string;
            }
            uses match-fields;
        }

        output {
            uses rpc-result;
        }
    }

    rpc read-table-entry {
        input {
            uses node;
            leaf table {
                type string;
            }
        }

        output {
            uses rpc-result;
            leaf-list content {
                type string; //Need to improve;
            }
        }
    }

    rpc add-action-profile-member {
        input {
            uses node;
            uses action-profile-member;
        }

        output {
            uses rpc-result;
        }
    }

    rpc modify-action-profile-member {
        input {
            uses node;
            uses action-profile-member;
        }

        output {
            uses rpc-result;
        }
    }

    rpc delete-action-profile-member {
        input {
            uses node;
            leaf action-profile {
                type string;
            }

            leaf member-id {
                type uint32;
            }
        }

        output {
            uses rpc-result;
        }
    }

    rpc read-action-profile-member {
        input {
            uses node;
            leaf action-profile {
                type string;
            }

            leaf member-id {
                type uint32;
            }
        }

        output {
            uses rpc-result;
            leaf-list member {
                type string;
            }
        }
    }

    rpc add-action-profile-group {
        input {
            uses node;
            uses action-profile-group;
        }

        output {
            uses rpc-result;
        }
    }

    //modify action profile group member, max_size cannot be modified after a group has been created
    rpc modify-action-profile-group {
        input {
            uses node;
            uses action-profile-group;
        }

        output {
            uses rpc-result;
        }
    }

    rpc delete-action-profile-group {
        input {
            uses node;
            uses action-profile-group;
        }

        output {
            uses rpc-result;
        }
    }

    rpc read-action-profile-group {
        input {
            uses node;
            leaf action-profile {
                type string;
            }

            leaf group-id {
                type uint32;
            }
        }

        output {
            uses rpc-result;
            leaf-list group {
                type string;
            }
        }
    }

	notification p4-packet-received {
        uses node;
        leaf payload {
    		type binary;
    	}
    }		
	
	rpc p4-transmit-packet {
        description "Sending packet out through p4 device.";
    	input {
            uses node;
			leaf payload {
				type binary;
		    }
    	}
    }
}
