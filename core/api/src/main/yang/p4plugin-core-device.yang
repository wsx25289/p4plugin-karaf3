module p4plugin-core-device {
    yang-version 1;
    namespace "urn:opendaylight:p4plugin:core:device";
    prefix "device";

    organization
        "ZTE corporation";

    contact
        "ding.rui@zte.com.cn";

    description
        "This module contains a set of type definitions and
         RPCs that are used across p4plugin";

    revision "2017-08-08" {
        description "Initial revision.";
    }

    import ietf-inet-types {
        prefix "inet";
        revision-date 2013-07-15;
    }

    import p4plugin-core-common {
        prefix "common";
        revision-date 2017-08-08;
    }
    
    //for poc
    import ietf-interfaces-test {
        prefix "test";
        revision-date 2017-09-08;
    }
    
    //grouping node {
    //    leaf node-id {
    //        type string;
    //    }
    //}

    //grouping grpc-server-ip {
    //    leaf ip {
    //        type inet:ipv4-address;
    //    }
    //}

    //grouping grpc-server-port {
    //    leaf port {
    //        type inet:port-number;
    //    }
    //}

    //grouping logic-device-id {
    //    leaf device-id {
    //        type uint64;
    //    }
    //}

    grouping device-config {
        leaf config-file {
            type string;
        }
    }

    grouping runtime-info {
        leaf runtime-file {
            type string;
        }
    }

    grouping device-identifier {
        //uses node;
        //uses grpc-server-ip;
        //uses grpc-server-port;
        //uses logic-device-id;
        uses test:p4-device;
        uses device-config;
        uses runtime-info;
    }

    rpc add-node {
        input {
            uses device-identifier;
        }

        output {
            uses common:rpc-result;
        }
    }

    rpc remove-node {
        input {
            uses test:node-identifier;
        }

        output {
            uses common:rpc-result;
        }
    }

    rpc query-nodes {
        output {
            uses common:rpc-result;
            leaf-list node {
                type string;
            }
        }
    }

    rpc set-pipeline-config {
        input {
            uses test:node-identifier;
        }

        output {
            uses common:rpc-result;
        }
    }

    rpc get-pipeline-config {
        input {
            uses test:node-identifier;
        }

        output {
            uses common:rpc-result;
            leaf p4-info {
                type string;
            }
        }
    }
}
