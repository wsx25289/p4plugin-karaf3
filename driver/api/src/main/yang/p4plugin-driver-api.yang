module p4plugin-driver-api {
    yang-version 1;
    namespace "urn:p4plugin:driver:api";
    prefix "p4plugin-driver-api";

    revision "2017-09-08" {
        description "Initial revision of driver model";
    }
    
    import ietf-yang-types {
      prefix yang;
      revision-date 2013-07-15;
    }
    import ietf-inet-types {
      prefix inet;
      revision-date 2013-07-15;
    }

    rpc read-device-interface {
        input {
            leaf device-id {
               type string;
            }
        }
        output {
            list device-interface {
               key "interface-name";            
               leaf interface-name {
                  type string;
               }
               
               leaf port-oper-status {
                  type enumeration {
                    enum "up" {
                      value 1;
                    }
                    enum "down" {
                      value 2;
                    }
                    enum "testing" {
                      value 3;
                    }
                    enum "unknown" {
                      value 4;
                    }
                  }
                  mandatory true;
               }
               
               leaf band-width {
                  type yang:gauge64;
                  units "bits/second";
               }
               
               container port-ipv4 {
                  leaf ipv4-forwarding {
                     type boolean;
                  }
            
                  list ipv4-address {
                     key "ip";
                     leaf ip {
                        type inet:ipv4-address-no-zone;
                        description
                          "The IPv6 address on the interface.";
                     }
                  } // ipv4-address
                } // container ipv4
               
               container port-ipv6 {
                  leaf ipv6-forwarding {
                     type boolean;
                     default false;
                  }
          
                  list ipv6-address {
                     key "ip";
                     leaf ip {
                        type inet:ipv6-address-no-zone;
                        description
                          "The IPv6 address on the interface.";
                     }
                  }
               } //container ipv6          
           } // device-interface
        } // output
    } // rpc
}
